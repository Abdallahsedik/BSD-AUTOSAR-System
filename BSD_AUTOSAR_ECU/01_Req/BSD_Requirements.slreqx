# BSD_Requirements

## BSD_Requirements!All Requirements: References to BSD_Requirements.xlsx (All Requirements) (Container)
Read-only references to Microsoft Excel document.

### SYS-FR: System Functional Requirements (Functional)
System-level functional requirements from SRS-PRJ-002

### FR-01: Object detection range (Functional)
System shall detect objects within 3.0 m in the blind spot zone

### FR-02: Trigger visual warning (Functional)
System shall enter WARNING state when object detected at distance < 3.0 m

### FR-03: Trigger critical alert (Functional)
System shall enter ALERT state when object detected AND turn signal active

### FR-04: Reset warning state (Functional)
System shall return to CLEAR state when distance exceeds 3.0 m

### FR-05: Actuate LED indicator (Functional)
System shall output LED warning signal (0=OFF, 1=ON)

### FR-06: Receive radar data (Functional)
System shall receive radar distance via CAN ID 0x200 (Left) and 0x201 (Right)

### FR-07: Receive vehicle speed (Functional)
System shall receive vehicle speed via CAN ID 0x100

### FR-08: Receive turn signal (Functional)
System shall receive turn signal status via CAN ID 0x3A0

### FR-09: Transmit HMI status (Functional)
System shall transmit warning status via CAN ID 0x300 every 20 ms

### FR-10: Transmit BCM command (Functional)
System shall transmit LED control via CAN ID 0x301 every 20 ms

### FR-11: Algorithm periodicity (Functional)
BSD algorithm shall execute every 20 ms

### FR-12: Receive gear status (Functional)
System shall receive gear status via CAN ID 0x1A0

### FR-13: Receive steering angle (Functional)
System shall receive steering angle via CAN ID 0x2E0

### FR-14: Highway suppression (Functional)
System shall ignore radar input when vehicle speed exceeds configured threshold

### FR-15: Report diagnostic failure (Functional)
System shall report a DTC when radar signal status is invalid

### SYS-NFR: System Non-Functional Requirements (Functional)
System non-functional requirements from SRS-PRJ-002

### NFR-01: Execution determinism (Functional)
BSD_Algorithm_SWC execution jitter shall not exceed ±2 ms

### NFR-02: Network bandwidth limit (Functional)
CAN bus load contributed by BSD_ECU shall not exceed 5% at 500 kbit/s

### NFR-03: CAN fault recovery (Functional)
System shall recover from a bus-off condition automatically

### NFR-04: Data integrity (Functional)
All inter-task shared data shall be protected against race conditions (RTOS critical sections / Priority Ceiling)

### NFR-05: Stack overflow detection (Functional)
Stack usage per task shall be monitored at runtime (stack overflow detection)

### VSG-FR: BSD_VehicleSignals_SWC Functional Requirements (Functional)
Requirements from SRS-PRJ-002-VSG

### VSG-FR-01: Read speed raw (Functional)
The SWC shall read Vehicle_Speed_Raw (CAN 0x100) every execution cycle

### VSG-FR-02: Read turn signal raw (Functional)
The SWC shall read Raw_turn_sig (CAN 0x3A0) every execution cycle

### VSG-FR-03: Read gear raw (Functional)
The SWC shall read Gear_Raw (CAN 0x1A0) every execution cycle

### VSG-FR-04: Read steering raw (Functional)
The SWC shall read Raw_steering (CAN 0x2E0) every execution cycle

### VSG-FR-05: Independent signal processing (Functional)
The SWC shall process the four signals independently; a failure of one signal shall not change the status of another

### VSG-FR-06: Scale speed (Functional)
The SWC shall convert speed using Vehicle_Speed = Vehicle_Speed_Raw x VSPD_RESOLUTION_KMH

### VSG-FR-07: Speed range check (Functional)
The SWC shall set Speed_Status to SIGNAL_FAIL when Vehicle_Speed_Raw is outside [VSPD_RAW_MIN; VSPD_RAW_MAX]

### VSG-FR-08: Scale steering (Functional)
The SWC shall convert steering angle using Steering_Angle = Raw_steering x STEER_RESOLUTION_DEG

### VSG-FR-09: Steering range check (Functional)
The SWC shall set Steering_Status to SIGNAL_FAIL when Raw_steering is outside [STEER_RAW_MIN; STEER_RAW_MAX]

### VSG-FR-10: Decode turn signal (Functional)
The SWC shall decode Raw_turn_sig to TurnSignal_T according to Section 5.2

### VSG-FR-11: Turn signal code check (Functional)
The SWC shall set TurnSignal_Status to SIGNAL_FAIL when Raw_turn_sig holds an undefined code

### VSG-FR-12: Decode gear (Functional)
The SWC shall decode Gear_Raw to Gear_T according to Section 5.2

### VSG-FR-13: Gear code check (Functional)
The SWC shall set Gear_Status to SIGNAL_FAIL when Gear_Raw holds an undefined code

### VSG-FR-14: Failsafe outputs (Functional)
When a signal status is SIGNAL_FAIL the SWC shall output the configured fail-safe value of that signal instead of a scaled or decoded value

### VSG-FR-15: Com timeout as FAIL (Functional)
A frame timeout shall be indicated by the Com module timeout replacement value; the SWC shall treat this value as SIGNAL_FAIL

### VSG-FR-16: Init all FAIL (Functional)
The SWC shall initialize all four signal statuses to SIGNAL_FAIL at startup and keep them until the first valid sample is received

### VSG-FR-17: Recovery hysteresis (Functional)
The SWC shall return a signal from SIGNAL_FAIL to SIGNAL_OK after VSG_RECOVERY_CNT consecutive valid samples

### VSG-FR-18: Atomic channel write (Functional)
The SWC shall write all elements of SRI_VehicleData in the same execution cycle so consumers never read values from different cycles

### VSG-FR-19: 20 ms period (Functional)
The SWC shall execute every 20 ms

### VSG-FR-20: No boolean status (Functional)
The SWC shall not use boolean types for any status signal; all validity information shall be exchanged as SignalStatus_T

### VSG-NFR: BSD_VehicleSignals_SWC Non-Functional Requirements (Functional)
Non-functional requirements from SRS-PRJ-002-VSG

### VSG-NFR-01: No dynamic memory (Functional)
The SWC shall not use dynamic memory allocation

### VSG-NFR-02: MISRA C compliance (Functional)
The SWC code shall comply with MISRA C:2012

### VSG-NFR-03: Determinism (Functional)
The SWC shall be deterministic: the same inputs and internal state shall produce the same outputs

### VSG-NFR-04: Bounded execution time (Functional)
The SWC execution time per cycle shall be bounded and shall not cause BSD_Algorithm_SWC to exceed its ±2 ms jitter limit

### VSG-NFR-05: Concurrency protection (Functional)
Shared data written by the SWC shall be protected against race conditions

### VSG-NFR-06: Minimal state holding (Functional)
The SWC shall hold only the state needed for validation: recovery counters per signal

### RIN-FR: BSD_RadarInput_SWC Functional Requirements (Functional)
Requirements from SRS-PRJ-002-RIN

### RIN-FR-01: Read left radar raw (Functional)
The SWC shall read Distance_Raw and Status_Raw of the left radar (CAN 0x200) every execution cycle

### RIN-FR-02: Read right radar raw (Functional)
The SWC shall read Distance_Raw and Status_Raw of the right radar (CAN 0x201) every execution cycle

### RIN-FR-03: Independent channels (Functional)
The SWC shall process the left and right channels independently; a failure on one side shall not affect the status of the other side

### RIN-FR-04: Sensor status code check (Functional)
The SWC shall set the channel status to RADAR_FAIL when Status_Raw does not equal the configured valid sensor code

### RIN-FR-05: Distance range check (Functional)
The SWC shall set the channel status to RADAR_FAIL when Distance_Raw is outside the configured range [RADAR_RAW_MIN; RADAR_RAW_MAX]

### RIN-FR-07: OK only if no failure (Functional)
The SWC shall set the channel status to RADAR_OK only when no failure condition of RIN-FR-04 or RIN-FR-05 is active

### RIN-FR-08: Scale distance (Functional)
The SWC shall convert Distance_Raw to meters using Distance = Distance_Raw x RADAR_RESOLUTION_M

### RIN-FR-09: Failsafe distance (Functional)
When the status is RADAR_FAIL the SWC shall output the configured fail-safe distance RADAR_DIST_FAILSAFE_M instead of a scaled value

### RIN-FR-10: Init both FAIL (Functional)
The SWC shall initialize both channels to RADAR_FAIL at startup and keep that status until the first valid sample is received

### RIN-FR-11: Recovery hysteresis (Functional)
The SWC shall return a channel from RADAR_FAIL to RADAR_OK once the configured number of consecutive valid samples (RADAR_RECOVERY_CNT) has been received

### RIN-FR-12: Atomic channel write (Functional)
The SWC shall write the distance and status of one channel together in the same execution cycle so the algorithm never reads a distance from one cycle with a status from another

### RIN-FR-13: 20 ms period (Functional)
The SWC shall execute every 20 ms matching the BSD algorithm period

### RIN-FR-14: No boolean status (Functional)
The SWC shall not use boolean types for any status signal; all validity information shall be exchanged as RadarStatus_T

### RIN-NFR: BSD_RadarInput_SWC Non-Functional Requirements (Functional)
Non-functional requirements from SRS-PRJ-002-RIN

### RIN-NFR-01: No dynamic memory (Functional)
The SWC shall not use dynamic memory allocation

### RIN-NFR-02: MISRA C compliance (Functional)
The SWC code shall comply with MISRA C:2012

### RIN-NFR-03: Determinism (Functional)
The SWC shall be deterministic: the same inputs and internal state shall always produce the same outputs

### RIN-NFR-04: Bounded execution time (Functional)
The SWC execution time per cycle shall be bounded and shall not cause the BSD algorithm to exceed its ±2 ms jitter limit

### RIN-NFR-05: Concurrency protection (Functional)
Shared data written by the SWC shall be protected against race conditions

### RIN-NFR-06: Minimal state holding (Functional)
The SWC shall hold only the state needed for validation: recovery counters per channel

### ALG-FR: BSD_Algorithm_SWC Functional Requirements (Functional)
Requirements from SRS-PRJ-002-ALG

### ALG-FR-01: Read input states (Functional)
The SWC shall read radar distances, statuses, vehicle speed, and turn signal states every execution cycle

### ALG-FR-02: Independent zone processing (Functional)
The SWC shall process the left and right blind spot zones independently

### ALG-FR-03: Radar fault handling (Functional)
The SWC shall treat radar distance as invalid (object not detected) if Status is RADAR_FAIL

### ALG-FR-04: Transition to WARNING (Functional)
The SWC shall transition the state from BSD_CLEAR to BSD_WARNING when object distance < 3.0 m

### ALG-FR-05: Transition to CLEAR (Functional)
The SWC shall transition the state from BSD_WARNING to BSD_CLEAR when object distance >= 3.0 m

### ALG-FR-06: Transition to ALERT (Functional)
The SWC shall transition the state to BSD_ALERT when the state is BSD_WARNING AND the turn signal is active on the same side

### ALG-FR-07: Revert to WARNING (Functional)
The SWC shall transition the state from BSD_ALERT to BSD_WARNING when the turn signal is deactivated

### ALG-FR-08: Highway suppression (Functional)
The SWC shall force the state to BSD_CLEAR if vehicle speed exceeds the VSPD_SUPPRESSION_THRESHOLD (Highway suppression)

### ALG-FR-09: Failsafe on speed fail (Functional)
The SWC shall force the state to BSD_CLEAR if Speed_Status is SIGNAL_FAIL (fail-safe behavior)

### ALG-FR-10: 20 ms period (Functional)
The SWC shall execute every 20 ms

### ALG-FR-11: No boolean types (Functional)
The SWC shall not use boolean types; all states shall be BSDState_T

### ALG-NFR: BSD_Algorithm_SWC Non-Functional Requirements (Functional)
Non-functional requirements from SRS-PRJ-002-ALG

### ALG-NFR-01: No dynamic memory (Functional)
The SWC shall not use dynamic memory allocation

### ALG-NFR-02: MISRA C compliance (Functional)
The SWC code shall comply with MISRA C:2012

### ALG-NFR-03: Execution jitter limit (Functional)
Execution jitter shall not exceed ±2 ms

### WRN-FR: BSD_Warning_SWC Functional Requirements (Functional)
Requirements from SRS-PRJ-002-WRN

### WRN-FR-01: Read BSD states (Functional)
The SWC shall read BSD_State_Left and BSD_State_Right every execution cycle

### WRN-FR-02: Publish states (Functional)
The SWC shall output the states directly to Warning_State_Left and Warning_State_Right

### WRN-FR-03: LED left on (Functional)
The SWC shall set LED_Left to LED_ON if BSD_State_Left is BSD_WARNING or BSD_ALERT

### WRN-FR-04: LED left off (Functional)
The SWC shall set LED_Left to LED_OFF if BSD_State_Left is BSD_CLEAR

### WRN-FR-05: LED right on (Functional)
The SWC shall set LED_Right to LED_ON if BSD_State_Right is BSD_WARNING or BSD_ALERT

### WRN-FR-06: LED right off (Functional)
The SWC shall set LED_Right to LED_OFF if BSD_State_Right is BSD_CLEAR

### WRN-FR-07: Atomic write (Functional)
The SWC shall write all elements of SRI_WarningOutput in the same execution cycle

### WRN-FR-08: 20 ms period (Functional)
The SWC shall execute every 20 ms

### WRN-FR-09: No boolean outputs (Functional)
The SWC shall not use boolean types for outputs; LED control shall be LedState_T (LED_ON or LED_OFF)

### WRN-NFR: BSD_Warning_SWC Non-Functional Requirements (Functional)
Non-functional requirements from SRS-PRJ-002-WRN

### WRN-NFR-01: No dynamic memory (Functional)
The SWC shall not use dynamic memory allocation

### WRN-NFR-02: MISRA C compliance (Functional)
The SWC code shall comply with MISRA C:2012

### WRN-NFR-03: Determinism (Functional)
The SWC shall be deterministic

### DIA-FR: BSD_Diagnostic_SWC Functional Requirements (Functional)
Requirements from SRS-PRJ-002-DIA

### DIA-FR-01: Read radar statuses (Functional)
The SWC shall read the Status of Radar Left and Radar Right every cycle

### DIA-FR-02: Read vehicle signal statuses (Functional)
The SWC shall read Speed_Status; TurnSignal_Status; Gear_Status and Steering_Status every cycle

### DIA-FR-03: Per-signal debounce counters (Functional)
The SWC shall maintain an independent debounce counter for each of the 6 monitored signals

### DIA-FR-04: Increment on FAIL (Functional)
If a signal status is FAIL the SWC shall increment its corresponding debounce counter

### DIA-FR-05: Reset on OK (Functional)
If a signal status is OK the SWC shall reset its corresponding debounce counter to 0

### DIA-FR-06: Report FAILED (Functional)
The SWC shall set the event status to DIAG_EVT_FAILED when the debounce counter reaches DIAG_DEBOUNCE_CNT

### DIA-FR-07: Report PASSED (Functional)
The SWC shall set the event status to DIAG_EVT_PASSED when the debounce counter is reset to 0

### DIA-FR-08: 20 ms period (Functional)
The SWC shall execute every 20 ms

### DIA-FR-09: No boolean statuses (Functional)
The SWC shall not use boolean types; all event statuses shall be DiagEventStatus_T

### DIA-NFR: BSD_Diagnostic_SWC Non-Functional Requirements (Functional)
Non-functional requirements from SRS-PRJ-002-DIA

### DIA-NFR-01: No dynamic memory (Functional)
The SWC shall not use dynamic memory allocation

### DIA-NFR-02: MISRA C compliance (Functional)
The SWC code shall comply with MISRA C:2012

### DIA-NFR-03: Bounded execution time (Functional)
The SWC execution time shall be bounded
